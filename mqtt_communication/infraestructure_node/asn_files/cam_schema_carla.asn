CAM DEFINITIONS AUTOMATIC TAGS ::= BEGIN

CAM ::= SEQUENCE {
    header ItsPduHeader,
    cam CoopAwareness
}

ItsPduHeader ::= SEQUENCE {
    protocolVersion INTEGER (0..255),
    messageID INTEGER (0..255),
    stationID INTEGER (0..4294967295)
}

CoopAwareness ::= SEQUENCE {
    generationDeltaTime INTEGER (0..65535),
    camParameters CamParameters
}

CamParameters ::= SEQUENCE {
    basicContainer BasicContainer
}

BasicContainer ::= SEQUENCE {
    stationType INTEGER (0..255),
    referencePosition ReferencePosition
}

ReferencePosition ::= SEQUENCE {
    latitude REAL,
    longitude REAL,
    positionConfidenceEllipse PosConfidenceEllipse,
    altitude Altitude
}

PosConfidenceEllipse ::= SEQUENCE {
    semiMajorConfidence INTEGER (0..255),
    semiMinorConfidence INTEGER (0..255),
    semiMajorOrientation INTEGER (0..3601)
}

Altitude ::= SEQUENCE {
    altitudeValue REAL,
    altitudeConfidence INTEGER (0..15)
}

END
